module cac {
    yang-version 1.1;
    namespace "urn:cac/cac";
    prefix "cac_cac";
    container foo {
        list bar {
            key "k2 k1"; // unsorted keys
            leaf k1 {
                type string;
            }
            leaf k2 {
                type string;
            }
            leaf attr1 {
                type string;
            }
            container subbar {
                leaf subattr1 {
                    type string;
                }
            }
        }
        container foo1 {
            choice c1 {
                container case1-container {
                    leaf cas1_leaf {
                        type string;
                    }
                }
                container case2-container {     
                    leaf cas2_leaf {
                        type string;
                    }
                }
                leaf cas3-leaf {
                    type string;
                }
            }
        }
        container foo2 {
            choice c2 {
                case cas1 {
                    container c2-1 {
                        leaf leaf-c2-1 {
                            type string;
                        }   
                    }
                }
                case cas2 {
                    container c2-2 {
                        leaf leaf-c2-2 {
                            type string;
                        }   
                    } 
                }
            }
            container c2-1 {
                leaf l1 {
                    type string;
                }
            }
        }
    }
}
