module dummy {
    yang-version 1.1;
    namespace "urn:dummy/dummy";
    prefix "dummy_dummy";
    container foo {
        list bar {
            key "k2 k1"; // unsorted keys
            leaf k1 {
                type string;
            }
            leaf k2 {
                type string;
            }
            leaf attr1 {
                type string;
            }
            container subbar {
                leaf subattr1 {
                    type string;
                }
            }
        }
        container foo1 {
            choice c1 {
                container case1-container {
                    leaf cas1_leaf {
                        type string;
                    }
                }
                container case2-container {     
                    leaf cas2_leaf {
                        type string;
                    }
                }
                leaf cas3-leaf {
                    type string;
                }
            }
        }
    }
}
