module sdcio_model {
  yang-version 1.1;
  namespace "urn:sdcio/model";
  prefix sdcio_model;

  import sdcio_model_ni {
    prefix sdcio_model_ni;
  }
  import sdcio_model_if {
    prefix sdcio_model_if;
  }
  import sdcio_model_choice {
    prefix sdcio_model_choice;
  }
  import sdcio_model_doublekey {
    prefix sdcio_model_doublekey;
  }
  import sdcio_model_mandatorykey {
    prefix sdcio_model_mandatorykey;
  }
  import sdcio_model_static_route {
    prefix sdcio_model_static_route;
  }
  import sdcio_model_leaflist {
    prefix sdcio_model_leaflist;
  }
  import sdcio_model_list_unique {
    prefix sdcio_model_list_unique;
  }
  import sdcio_model_list_minmax {
    prefix sdcio_model_list_minmax;
  }
  import sdcio_model_deref {
    prefix sdcio_model_deref;
  }
  import sdcio_model_identity {
    prefix sdcio_model_identity;
  }
  import sdcio_model_leafref {
    prefix sdcio_model_leafref;
  }
  import sdcio_model_count {
    prefix sdcio_model_count;
  }

  description
    "This is the test schema for sdcio";

  revision 2024-06-03 {
    description
      "Test schema first attempt";
  }

  uses sdcio_model_count:count-top;
  uses sdcio_model_if:interface-top;
  uses sdcio_model_ni:network-instance-top;
  uses sdcio_model_choice:choicecase-top;
  uses sdcio_model_doublekey:doublekey-top;
  uses sdcio_model_mandatorykey:mandatorykey-top;
  uses sdcio_model_static_route:static-route-top;
  uses sdcio_model_leaflist:leaflist-top;
  uses sdcio_model_list_unique:list-unique-top;
  uses sdcio_model_list_minmax:list-minmax-top;
  uses sdcio_model_deref:deref-top;
  uses sdcio_model_identity:identityref-top;
  uses sdcio_model_leafref:leafref-top;
  leaf patterntest {
    type string {
      length "7..10";
      pattern 'hallo [0-9a-fA-F]*';
      // pattern 'hallo DU' {
      //  // modifier invert-match;
      // }
    }
  }
  leaf emptyconf {
    type empty;
  }
  leaf rangetestsigned {
    type int32 {
      range "-3000..-60 | -50 | -32..-1 | 10..300";
    }
  }
  leaf rangetestunsigned {
    type uint32 {
      range "10..300 | 5000..5020 | 9999";
    }
  }
  leaf-list rangetestLeaflist {
    type uint32 {
      range "10..300 | 5000..5020 | 9999";
    }
  }
  leaf unionpatterntest {
    type union {
      type string {
        pattern 'hallo [0-9a-fA-F]*';
      }
      type uint32;
    }
    default "99";
  }
  leaf unionlengthtest {
    type union {
      type string {
        length "7..10";
      }
      type uint32;
    }
  }
  leaf unionrangetest {
    type union {
      type uint32 {
        range "10..300";
      }
      type string;
    }
  }
  leaf unionleafreftest {
    type union {
      type leafref {
        path "/interface/name";
      }
      type string;
    }
  }
  leaf unionoptionalleafreftest {
    type union {
      type leafref {
        path "/interface/name";
        require-instance false;
      }
      type string;
    }
  }
}
