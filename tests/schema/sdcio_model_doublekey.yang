module sdcio_model_doublekey {
  yang-version 1.1;
  namespace "urn:sdcio/model_doublekey";
  prefix sdcio_model_doublekey;

  description
    "This is part of the test schema for sdcio";

  revision 2024-06-03 {
    description
      "Test schema first attempt";
  }

  grouping doublekey-top {
    list doublekey {
      description
        "here we have a container with two keys";
      key "key2 key1";
      leaf key2 {
        type string {
          pattern 'k2[a-zA-Z0-9.]+';
        }
      }
      leaf key1 {
        type string {
          pattern 'k1[a-zA-Z0-9.]+';
        }
      }
      leaf mandato {
        type string;
        mandatory true;
      }
      container cont {
        description
          "just a simple container under a double keyed item";
        leaf value1 {
          type string;
        }
        leaf value2 {
          type string;
        }
      }
    }
  }
}
