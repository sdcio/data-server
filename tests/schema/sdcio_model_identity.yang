module sdcio_model_identity {
  yang-version 1.1;
  namespace "urn:sdcio/model_identity";
  prefix sdcio_identity;

  import sdcio_model_identity_base {
    prefix identity_base;
  }

  identity otherAlgo {
    base identity_base:crypto-alg;
    base identity_base:public-key;
    description
      "other Algo";
  }

  grouping identityref-top {
    container identityref {
      leaf cryptoA {
        type identityref {
          base identity_base:crypto-alg;
        }
      }
      leaf cryptoB {
        type identityref {
          base identity_base:crypto-alg;
        }
      }
    }
    list intentityrefkey {
      key "crypto";
      leaf crypto {
        type identityref {
          base identity_base:crypto-alg;
        }
      }
      leaf description {
        type string;
      }
    }

    // must exercises Navigate prefix stripping: the key predicate value is
    // derived from an identityref leaf via current(), which YangString()
    // returns as "prefix:value".  Navigate must strip that prefix before
    // calling NavigateSdcpbPath, otherwise the list entry cannot be found.
    // The sdcio_identity: self-prefix on path steps is a non-standard alias
    // (the importing module uses a different alias), exercising the strip.
    container identityref-must-test {
      leaf crypto-ref {
        type identityref {
          base identity_base:crypto-alg;
        }
      }
      must "../sdcio_identity:intentityrefkey[sdcio_identity:crypto=current()/sdcio_identity:crypto-ref]/sdcio_identity:description != ''" {
        error-message "intentityrefkey entry for crypto-ref must exist with non-empty description";
      }
    }

    // leafref exercises resolveLeafrefKeyPath identityref key normalisation:
    // the key predicate current()/../identityref/cryptoA resolves to an
    // IdentityrefVal; tv.ToString() must be used (not tv.GetStringVal()).
    leaf intentityrefkey-ref {
      type leafref {
        path "../intentityrefkey[crypto=current()/../identityref/cryptoA]/description";
      }
    }
  }
}
