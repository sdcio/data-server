module sdcio_model_count {
  yang-version 1.1;
  namespace "urn:sdcio/model_count";
  prefix sdcio_model_count;

  grouping count-top {
    container count {
      list server {
        key "keyAttr";
        leaf keyAttr {
          type string;
        }
        leaf attr {
          type string;
        }
      }
      must 'count(./server) = 2' {
        error-message "Relative Path - There must be exactly 2 server entries.";
      }
      must 'count(/count/server) = 2' {
        error-message "Absolute Path - There must be exactly 2 server entries.";
      }
    }
    container count-doublekey {
      list server {
        key "keyAttr1 keyAttr2";
        leaf keyAttr1 {
          type string;
        }
        leaf keyAttr2 {
          type string;
        }
        leaf attr {
          type string;
        }
      }
      must 'count(./server) = 2' {
        error-message "Relative Path - There must be exactly 2 server entries.";
      }
      must 'count(/count-doublekey/server) = 2' {
        error-message "Absolute Path - There must be exactly 2 server entries.";
      }
    }
    container must-sibling {
      list server {
        key "keyAttr";
        leaf keyAttr {
          type string;
        }
        leaf val1 {
          type uint8;
        }
        leaf val2 {
          type uint8;
        }
        must 'val1 + val2 <= 128' {
          error-message "val1 + val2 must not exceed 128.";
        }
      }
    }
    container count-leaflist {
      leaf-list flag {
        type string;
      }
      must 'count(./flag[text()="all"]) = 0 or count(./flag) = 1' {
        error-message "If 'all' is set, it must be the only flag.";
      }
    }
  }
}
