module sdcio_model_deref {
  yang-version 1.1;
  namespace "urn:sdcio/model_deref";
  prefix sdcio_model_deref;

  description
    "This is part of the test schema for sdcio";

  revision 2024-09-09 {
    description
      "Test schema first attempt";
  }

  grouping deref-top {
    container mgmt-interface {
      leaf name {
        type leafref {
          path "/interface/name";
        }
      }
      leaf type {
        type leafref {
          path "/interface[name=current()/../name]/interface-type";
        }
        must 'deref(.)/../admin-state = "enable"' {
          error-message "The management interface cannot be disabled.";
        }
      }
    }
  }
}
