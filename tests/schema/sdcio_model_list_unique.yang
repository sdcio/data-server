module sdcio_model_list_unique {
  yang-version 1.1;
  namespace "urn:sdcio/model_list_unique";
  prefix sdcio_model_list_unique;

  grouping list-unique-top {
    container list-unique {
      list server {
        key "name";
        unique "ip port";
        unique "description";
        leaf name {
          type string;
        }
        leaf ip {
          type string;
        }
        leaf port {
          type uint16;
        }
        leaf description {
          type string;
        }
      }
      list plain {
        key "name";
        leaf name {
          type string;
        }
        leaf value {
          type string;
        }
      }
      list multi-seg {
        key "name";
        unique "sub/field";
        leaf name {
          type string;
        }
        container sub {
          leaf field {
            type string;
          }
        }
      }
    }
  }
}
